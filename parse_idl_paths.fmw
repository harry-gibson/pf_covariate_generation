FME workspace parse_idl_paths.fmw

Parameters:
- SourceDataset_TEXTLINE = $(FME_MF_DIR)idl_code\pf_v*.pro   # Source Text File(s)

Readers:
- TEXTLINE_1: TEXTLINE from $(SourceDataset_TEXTLINE)

text_line (reader TEXTLINE_1)
    attributes: text_line_data buffer
    -> AttributeExposer
AttributeExposer
    ATTR_LIST = fme_basename
    -> AttributeTrimmer
AttributeTrimmer
    TRIM_TYPE = Both
    TRIM_TO_NONE = Yes
    SRC_ATTRS = fme_basename,text_line_data
    -> TestFilter
TestFilter
    DEFAULT_VALUE = <UNFILTERED>
    TEST_LIST:
      BOOL_OP,OR,COMPOSITE_TEST,<Unused>,TEST_CLAUSE,"TEST @Value(text_line_data) CONTAINS var_1_adjustment_factor =
      TEST @Value(text_line_data) CONTAINS var_2_adjustment_factor =",@Value(text_line_data) = var_1_adjustment_factor =,BOOL_OP,OR,COMPOSITE_TEST,<Unused>,TEST_CLAUSE,"TEST @Value(text_line_data) BEGINS_WITH input_path
      TEST @Value(text_line_data) BEGINS_WITH input_file
      TEST @Value(text_line_data) BEGINS_WITH input_suffix",@Value(text_line_data) BEGINS_WITH input_path
    <UNFILTERED> -> TestFilter__Unfiltered_
    @Value(text_line_data) = var_1_adjustment_factor = -> TestFilter__Value_text_line_data____var_1_adjustment_factor__
    @Value(text_line_data) BEGINS_WITH input_path -> TestFilter__Value_text_line_data__BEGINS_WITH_input_path
TestFilter__Value_text_line_data____var_1_adjustment_factor__: Inspector
TestFilter__Value_text_line_data__BEGINS_WITH_input_path: Inspector
TestFilter__Unfiltered_: Inspector
